--==========================================================================
--
--	ZX7250FABRIC.MIB
--
--	ZNYX ZX7250FABRIC SNMP MIB
--
--==========================================================================
--
--	(c) Copyright 2001 ZNYX Networks, Inc.
--	All rights reserved.
--
--==========================================================================


	ZX7250FABRIC-MIB DEFINITIONS ::= BEGIN

	IMPORTS
		enterprises, NetworkAddress, IpAddress, Counter,
		Gauge, TimeTicks, OBJECT-TYPE
			FROM RFC1155-SMI
		znyxProductSpecificMib
			FROM ZNYX-MIB;

	-- Conventions

	DisplayString ::= OCTET STRING



	znyxPsMibZX7250FABRIC		OBJECT IDENTIFIER ::= { znyxProductSpecificMib 13 }

	zZX7250FABRICGeoPins OBJECT-TYPE
		SYNTAX  DisplayString (SIZE (0..255))
		ACCESS  read-only
		STATUS  mandatory
		DESCRIPTION
			"This object returns a string identifying
			 the shelf and the slot within the shelf
			 the switch is located in."
		::= { znyxPsMibZX7250FABRIC 1 }

	zZX7250FABRICInternalFaultLedControl OBJECT-TYPE
		SYNTAX  INTEGER {
			off(1),
			on(2),
			other(3)	-- driven by other control
			}
		ACCESS  read-write
		STATUS  mandatory
		DESCRIPTION
			"This object is used to determine how the
			 Internal Fault LED is driven."
		::= { znyxPsMibZX7250FABRIC 2 }

	zZX7250FABRICInternalFaultLedStatus OBJECT-TYPE
		SYNTAX  INTEGER {
			off(1),
			on(2)
			}
		ACCESS  read-only
		STATUS  mandatory
		DESCRIPTION
			"This object is used to determine the
			 current Internal Fault LED status."
		::= { znyxPsMibZX7250FABRIC 3 }

	zZX7250FABRICExternalFaultLedControl OBJECT-TYPE
		SYNTAX  INTEGER {
			off(1),
			on(2),
			other(3)	-- driven by other control
			}
		ACCESS  read-write
		STATUS  mandatory
		DESCRIPTION
			"This object is used to determine how the
			 External Fault LED is driven."
		::= { znyxPsMibZX7250FABRIC 4 }

	zZX7250FABRICExternalFaultLedStatus OBJECT-TYPE
		SYNTAX  INTEGER {
			off(1),
			on(2)
			}
		ACCESS  read-only
		STATUS  mandatory
		DESCRIPTION
			"This object is used to determine the
			 current External Fault LED status."
		::= { znyxPsMibZX7250FABRIC 5 }

	zZX7250FABRICOpenArchVersion OBJECT-TYPE
   		SYNTAX DisplayString
   		ACCESS read-only
   	 	STATUS     mandatory
   		DESCRIPTION
    	    		"The Open Architect software version."
    		::= { znyxPsMibZX7250FABRIC 6 }

	zZX7250FABRICLinkCtrlTable OBJECT-TYPE
	    	SYNTAX      SEQUENCE OF ZZX7250FABRICLinkCtrlEntry
  		ACCESS  not-accessible
    		STATUS      mandatory
    		DESCRIPTION
      	    	"A table containing link control information for each port
		       available on the device."
    		::= { znyxPsMibZX7250FABRIC 7 }

	zZX7250FABRICLinkCtrlEntry OBJECT-TYPE
 		SYNTAX      ZZX7250FABRICLinkCtrlEntry
    		ACCESS  not-accessible
    		STATUS      mandatory
    		DESCRIPTION
      		"Link control information for each port available on the
			 device."
   		INDEX   { zZX7250FABRICLinkCtrlPort }
    		::= { zZX7250FABRICLinkCtrlTable 1 }

 	ZZX7250FABRICLinkCtrlEntry ::=
  		SEQUENCE {
			zZX7250FABRICLinkCtrlPort
				INTEGER,
			zZX7250FABRICLinkCtrlState
				INTEGER,
			zZX7250FABRICLinkCtrlSpeed
				INTEGER
    		}

	zZX7250FABRICLinkCtrlPort OBJECT-TYPE
		SYNTAX      INTEGER (1..65535)
		ACCESS  not-accessible
		STATUS      mandatory
		DESCRIPTION
		"The port number associated with this Link Control entry."
		::= { zZX7250FABRICLinkCtrlEntry 1 }

	zZX7250FABRICLinkCtrlState OBJECT-TYPE
    		SYNTAX      INTEGER { up (1), down (2) }
    		ACCESS  read-write
    		STATUS      mandatory
    		DESCRIPTION
        		"The link control state of the port."
    		::= { zZX7250FABRICLinkCtrlEntry 2 }

	zZX7250FABRICLinkCtrlSpeed OBJECT-TYPE
    		SYNTAX      INTEGER  { auto(1), n100fd(2), n100hd(3), n10fd (4), n10hd(5), n1000fd(6), n1000hd(7), n10000fd(8) }
    		ACCESS  read-write
    		STATUS      mandatory
    		DESCRIPTION
        		"The link control speed of the port. Changes to this speed
			 require the port to be in the down state."
    		::= { zZX7250FABRICLinkCtrlEntry 3 }

	-- Vital Product Data (VPD)

	zZX7250FABRICVPDPN OBJECT-TYPE
   		SYNTAX DisplayString
   		ACCESS read-only
   	 	STATUS     mandatory
   		DESCRIPTION
    	    		"The VPD Part Number."
    		::= { znyxPsMibZX7250FABRIC 8 }

	zZX7250FABRICVPDSN OBJECT-TYPE
   		SYNTAX DisplayString
   		ACCESS read-only
   	 	STATUS     mandatory
   		DESCRIPTION
    	    		"The VPD Serial Number."
    		::= { znyxPsMibZX7250FABRIC 9 }

	zZX7250FABRICVPDV0 OBJECT-TYPE
   		SYNTAX DisplayString
   		ACCESS read-only
   	 	STATUS     mandatory
   		DESCRIPTION
    	    		"The VPD Mac Address."
    		::= { znyxPsMibZX7250FABRIC 10 }

	zZX7250FABRICVPDV1 OBJECT-TYPE
   		SYNTAX DisplayString
   		ACCESS read-only
   	 	STATUS     mandatory
   		DESCRIPTION
    	    		"The VPD Mac Address Number."
    		::= { znyxPsMibZX7250FABRIC 11 }

	zZX7250FABRICVPDV2 OBJECT-TYPE
   		SYNTAX DisplayString
   		ACCESS read-only
   	 	STATUS     mandatory
   		DESCRIPTION
    	    		"The PPC 82xx Memory Subsystem."
    		::= { znyxPsMibZX7250FABRIC 12 }

	zZX7250FABRICVPDV3 OBJECT-TYPE
   		SYNTAX DisplayString
   		ACCESS read-only
   	 	STATUS     mandatory
   		DESCRIPTION
    	    		"The BCM 56xx Memory Subsystem."
    		::= { znyxPsMibZX7250FABRIC 13 }

	zZX7250FABRICVPDV4 OBJECT-TYPE
   		SYNTAX DisplayString
   		ACCESS read-only
   	 	STATUS     mandatory
   		DESCRIPTION
    	    		"The Boot Flash Subsystem."
    		::= { znyxPsMibZX7250FABRIC 14 }

	zZX7250FABRICVPDV5 OBJECT-TYPE
   		SYNTAX DisplayString
   		ACCESS read-only
   	 	STATUS     mandatory
   		DESCRIPTION
    	    		"The Application Flash Subsystem."
    		::= { znyxPsMibZX7250FABRIC 15 }

	zZX7250FABRICVPDV6 OBJECT-TYPE
   		SYNTAX DisplayString
   		ACCESS read-only
   	 	STATUS     mandatory
   		DESCRIPTION
    	    		"The Firmware Revision."
    		::= { znyxPsMibZX7250FABRIC 16 }

	zZX7250FABRICVPDV7 OBJECT-TYPE
   		SYNTAX DisplayString
   		ACCESS read-only
   	 	STATUS     mandatory
   		DESCRIPTION
    	    		"The Reset Counter."
    		::= { znyxPsMibZX7250FABRIC 17 }

	zZX7250FABRICVPDV8 OBJECT-TYPE
   		SYNTAX DisplayString
   		ACCESS read-only
   	 	STATUS     mandatory
   		DESCRIPTION
    	    		"The Kernel Runtime."
    		::= { znyxPsMibZX7250FABRIC 18 }

	zZX7250FABRICVPDV9 OBJECT-TYPE
   		SYNTAX DisplayString
   		ACCESS read-only
   	 	STATUS     mandatory
   		DESCRIPTION
    	    		"The VPD Revision."
    		::= { znyxPsMibZX7250FABRIC 19 }

	zZX7250FABRICVPDVA OBJECT-TYPE
   		SYNTAX DisplayString
   		ACCESS read-only
   	 	STATUS     mandatory
   		DESCRIPTION
    	    		"The Adapter ID."
    		::= { znyxPsMibZX7250FABRIC 20 }

	zZX7250FABRICVPDVB OBJECT-TYPE
   		SYNTAX DisplayString
   		ACCESS read-only
   	 	STATUS     mandatory
   		DESCRIPTION
    	    		"The Model Number."
    		::= { znyxPsMibZX7250FABRIC 21 }

	zZX7250FABRICVPDVS OBJECT-TYPE
   		SYNTAX DisplayString
   		ACCESS read-only
   	 	STATUS     mandatory
   		DESCRIPTION
    	    		"The Logical Slot Number."
    		::= { znyxPsMibZX7250FABRIC 22 }

	zZX7250FABRICVPDVT OBJECT-TYPE
   		SYNTAX DisplayString
   		ACCESS read-only
   	 	STATUS     mandatory
   		DESCRIPTION
    	    		"The Geographical Shelf Address."
    		::= { znyxPsMibZX7250FABRIC 23 }

	zZX7250FABRICVPDVP OBJECT-TYPE
   		SYNTAX DisplayString
   		ACCESS read-only
   	 	STATUS     mandatory
   		DESCRIPTION
    	    		"The IPMC Version."
    		::= { znyxPsMibZX7250FABRIC 24 }

	zZX7250FABRICVPDVM OBJECT-TYPE
   		SYNTAX DisplayString
   		ACCESS read-only
   	 	STATUS     mandatory
   		DESCRIPTION
    	    		"The Main CPLD Version."
    		::= { znyxPsMibZX7250FABRIC 25 }

	zZX7250FABRICVPDVR OBJECT-TYPE
   		SYNTAX DisplayString
   		ACCESS read-only
   	 	STATUS     mandatory
   		DESCRIPTION
    	    		"The Reset CPLD Version."
    		::= { znyxPsMibZX7250FABRIC 26 }

	zZX7250FABRICVPDVL OBJECT-TYPE
   		SYNTAX DisplayString
   		ACCESS read-only
   	 	STATUS     mandatory
   		DESCRIPTION
    	    		"The LED CPLD Version."
    		::= { znyxPsMibZX7250FABRIC 27 }

	zZX7250FABRICVPDVZ OBJECT-TYPE
   		SYNTAX DisplayString
   		ACCESS read-only
   	 	STATUS     mandatory
   		DESCRIPTION
    	    		"The ZMON Version."
    		::= { znyxPsMibZX7250FABRIC 28 }

	zZX7250FABRICVPDY1 OBJECT-TYPE
   		SYNTAX DisplayString
   		ACCESS read-only
   	 	STATUS     mandatory
   		DESCRIPTION
    	    		"The Manufacturer ID."
    		::= { znyxPsMibZX7250FABRIC 29 }

	zZX7250FABRICVPDY2 OBJECT-TYPE
   		SYNTAX DisplayString
   		ACCESS read-only
   	 	STATUS     mandatory
   		DESCRIPTION
    	    		"The Board ID."
    		::= { znyxPsMibZX7250FABRIC 30 }

	zZX7250FABRICVPDY3 OBJECT-TYPE
   		SYNTAX DisplayString
   		ACCESS read-only
   	 	STATUS     mandatory
   		DESCRIPTION
    	    		"The Data CLEI."
    		::= { znyxPsMibZX7250FABRIC 31 }

	zZX7250FABRICVPDY4 OBJECT-TYPE
   		SYNTAX DisplayString
   		ACCESS read-only
   	 	STATUS     mandatory
   		DESCRIPTION
    	    		"The Data PEC."
    		::= { znyxPsMibZX7250FABRIC 32 }

	zZX7250FABRICVPDY5 OBJECT-TYPE
   		SYNTAX DisplayString
   		ACCESS read-only
   	 	STATUS     mandatory
   		DESCRIPTION
    	    		"The Release Number."
    		::= { znyxPsMibZX7250FABRIC 33 }

	END
