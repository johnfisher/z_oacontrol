--==========================================================================
--
--	ZX7100FABRIC.MIB
--
--	ZNYX ZX7100FABRIC SNMP MIB
--
--==========================================================================
--
--	(c) Copyright 2001 ZNYX Networks, Inc.
--	All rights reserved.
--
--==========================================================================


	ZX7100FABRIC-MIB DEFINITIONS ::= BEGIN

	IMPORTS
		enterprises, NetworkAddress, IpAddress, Counter,
		Gauge, TimeTicks, OBJECT-TYPE
			FROM RFC1155-SMI
		znyxProductSpecificMib
			FROM ZNYX-MIB;

	-- Conventions

	DisplayString ::= OCTET STRING



	znyxPsMibZX7100FABRIC		OBJECT IDENTIFIER ::= { znyxProductSpecificMib 8 }

	zZX7100FABRICGeoPins OBJECT-TYPE
		SYNTAX  DisplayString (SIZE (0..255))
		ACCESS  read-only
		STATUS  mandatory
		DESCRIPTION
			"This object returns a string identifying
			 the shelf and the slot within the shelf
			 the switch is located in."
		::= { znyxPsMibZX7100FABRIC 1 }

	zZX7100FABRICInternalFaultLedControl OBJECT-TYPE
		SYNTAX  INTEGER {
			off(1),
			on(2),
			other(3)	-- driven by other control
			}
		ACCESS  read-write
		STATUS  mandatory
		DESCRIPTION
			"This object is used to determine how the
			 Internal Fault LED is driven."
		::= { znyxPsMibZX7100FABRIC 2 }

	zZX7100FABRICInternalFaultLedStatus OBJECT-TYPE
		SYNTAX  INTEGER {
			off(1),
			on(2)
			}
		ACCESS  read-only
		STATUS  mandatory
		DESCRIPTION
			"This object is used to determine the
			 current Internal Fault LED status."
		::= { znyxPsMibZX7100FABRIC 3 }

	zZX7100FABRICExternalFaultLedControl OBJECT-TYPE
		SYNTAX  INTEGER {
			off(1),
			on(2),
			other(3)	-- driven by other control
			}
		ACCESS  read-write
		STATUS  mandatory
		DESCRIPTION
			"This object is used to determine how the
			 External Fault LED is driven."
		::= { znyxPsMibZX7100FABRIC 4 }

	zZX7100FABRICExternalFaultLedStatus OBJECT-TYPE
		SYNTAX  INTEGER {
			off(1),
			on(2)
			}
		ACCESS  read-only
		STATUS  mandatory
		DESCRIPTION
			"This object is used to determine the
			 current External Fault LED status."
		::= { znyxPsMibZX7100FABRIC 5 }

	zZX7100FABRICOpenArchVersion OBJECT-TYPE
   		SYNTAX DisplayString
   		ACCESS read-only
   	 	STATUS     mandatory
   		DESCRIPTION
    	    		"The Open Architect software version."
    		::= { znyxPsMibZX7100FABRIC 6 }

	zZX7100FABRICLinkCtrlTable OBJECT-TYPE
	    	SYNTAX      SEQUENCE OF ZZX7100FABRICLinkCtrlEntry
  		ACCESS  not-accessible
    		STATUS      mandatory
    		DESCRIPTION
      	    	"A table containing link control information for each port
		       available on the device."
    		::= { znyxPsMibZX7100FABRIC 7 }

	zZX7100FABRICLinkCtrlEntry OBJECT-TYPE
 		SYNTAX      ZZX7100FABRICLinkCtrlEntry
    		ACCESS  not-accessible
    		STATUS      mandatory
    		DESCRIPTION
      		"Link control information for each port available on the
			 device."
   		INDEX   { zZX7100FABRICLinkCtrlPort }
    		::= { zZX7100FABRICLinkCtrlTable 1 }

 	ZZX7100FABRICLinkCtrlEntry ::=
  		SEQUENCE {
			zZX7100FABRICLinkCtrlPort
				INTEGER,
			zZX7100FABRICLinkCtrlState
				INTEGER,
			zZX7100FABRICLinkCtrlSpeed
				INTEGER
    		}

	zZX7100FABRICLinkCtrlPort OBJECT-TYPE
		SYNTAX      INTEGER (1..65535)
		ACCESS  not-accessible
		STATUS      mandatory
		DESCRIPTION
		"The port number associated with this Link Control entry."
		::= { zZX7100FABRICLinkCtrlEntry 1 }

	zZX7100FABRICLinkCtrlState OBJECT-TYPE
    		SYNTAX      INTEGER { up (1), down (2) }
    		ACCESS  read-write
    		STATUS      mandatory
    		DESCRIPTION
        		"The link control state of the port."
    		::= { zZX7100FABRICLinkCtrlEntry 2 }

	zZX7100FABRICLinkCtrlSpeed OBJECT-TYPE
    		SYNTAX      INTEGER  { auto(1), n100fd(2), n100hd(3), n10fd (4), n10hd(5), n1000fd(6), n1000hd(7), n10000fd(8) }
    		ACCESS  read-write
    		STATUS      mandatory
    		DESCRIPTION
        		"The link control speed of the port. Changes to this speed
			 require the port to be in the down state."
    		::= { zZX7100FABRICLinkCtrlEntry 3 }

	-- Vital Product Data (VPD)

	zZX7100FABRICVPDPN OBJECT-TYPE
   		SYNTAX DisplayString
   		ACCESS read-only
   	 	STATUS     mandatory
   		DESCRIPTION
    	    		"The VPD Part Number."
    		::= { znyxPsMibZX7100FABRIC 8 }

	zZX7100FABRICVPDSN OBJECT-TYPE
   		SYNTAX DisplayString
   		ACCESS read-only
   	 	STATUS     mandatory
   		DESCRIPTION
    	    		"The VPD Serial Number."
    		::= { znyxPsMibZX7100FABRIC 9 }

	zZX7100FABRICVPDV0 OBJECT-TYPE
   		SYNTAX DisplayString
   		ACCESS read-only
   	 	STATUS     mandatory
   		DESCRIPTION
    	    		"The VPD Mac Address."
    		::= { znyxPsMibZX7100FABRIC 10 }

	zZX7100FABRICVPDV1 OBJECT-TYPE
   		SYNTAX DisplayString
   		ACCESS read-only
   	 	STATUS     mandatory
   		DESCRIPTION
    	    		"The VPD Mac Address Number."
    		::= { znyxPsMibZX7100FABRIC 11 }

	zZX7100FABRICVPDV2 OBJECT-TYPE
   		SYNTAX DisplayString
   		ACCESS read-only
   	 	STATUS     mandatory
   		DESCRIPTION
    	    		"The PPC 82xx Memory Subsystem."
    		::= { znyxPsMibZX7100FABRIC 12 }

	zZX7100FABRICVPDV3 OBJECT-TYPE
   		SYNTAX DisplayString
   		ACCESS read-only
   	 	STATUS     mandatory
   		DESCRIPTION
    	    		"The BCM 56xx Memory Subsystem."
    		::= { znyxPsMibZX7100FABRIC 13 }

	zZX7100FABRICVPDV4 OBJECT-TYPE
   		SYNTAX DisplayString
   		ACCESS read-only
   	 	STATUS     mandatory
   		DESCRIPTION
    	    		"The Boot Flash Subsystem."
    		::= { znyxPsMibZX7100FABRIC 14 }

	zZX7100FABRICVPDV5 OBJECT-TYPE
   		SYNTAX DisplayString
   		ACCESS read-only
   	 	STATUS     mandatory
   		DESCRIPTION
    	    		"The Application Flash Subsystem."
    		::= { znyxPsMibZX7100FABRIC 15 }

	zZX7100FABRICVPDV6 OBJECT-TYPE
   		SYNTAX DisplayString
   		ACCESS read-only
   	 	STATUS     mandatory
   		DESCRIPTION
    	    		"The Firmware Revision."
    		::= { znyxPsMibZX7100FABRIC 16 }

	zZX7100FABRICVPDV7 OBJECT-TYPE
   		SYNTAX DisplayString
   		ACCESS read-only
   	 	STATUS     mandatory
   		DESCRIPTION
    	    		"The Reset Counter."
    		::= { znyxPsMibZX7100FABRIC 17 }

	zZX7100FABRICVPDV8 OBJECT-TYPE
   		SYNTAX DisplayString
   		ACCESS read-only
   	 	STATUS     mandatory
   		DESCRIPTION
    	    		"The Kernel Runtime."
    		::= { znyxPsMibZX7100FABRIC 18 }

	zZX7100FABRICVPDV9 OBJECT-TYPE
   		SYNTAX DisplayString
   		ACCESS read-only
   	 	STATUS     mandatory
   		DESCRIPTION
    	    		"The VPD Revision."
    		::= { znyxPsMibZX7100FABRIC 19 }

	zZX7100FABRICVPDVA OBJECT-TYPE
   		SYNTAX DisplayString
   		ACCESS read-only
   	 	STATUS     mandatory
   		DESCRIPTION
    	    		"The Adapter ID."
    		::= { znyxPsMibZX7100FABRIC 20 }

	zZX7100FABRICVPDVB OBJECT-TYPE
   		SYNTAX DisplayString
   		ACCESS read-only
   	 	STATUS     mandatory
   		DESCRIPTION
    	    		"The Model Number."
    		::= { znyxPsMibZX7100FABRIC 21 }

	zZX7100FABRICVPDVS OBJECT-TYPE
   		SYNTAX DisplayString
   		ACCESS read-only
   	 	STATUS     mandatory
   		DESCRIPTION
    	    		"The Logical Slot Number."
    		::= { znyxPsMibZX7100FABRIC 22 }

	zZX7100FABRICVPDVT OBJECT-TYPE
   		SYNTAX DisplayString
   		ACCESS read-only
   	 	STATUS     mandatory
   		DESCRIPTION
    	    		"The Geographical Shelf Address."
    		::= { znyxPsMibZX7100FABRIC 23 }

	zZX7100FABRICVPDVP OBJECT-TYPE
   		SYNTAX DisplayString
   		ACCESS read-only
   	 	STATUS     mandatory
   		DESCRIPTION
    	    		"The IPMC Version."
    		::= { znyxPsMibZX7100FABRIC 24 }

	zZX7100FABRICVPDVM OBJECT-TYPE
   		SYNTAX DisplayString
   		ACCESS read-only
   	 	STATUS     mandatory
   		DESCRIPTION
    	    		"The Main CPLD Version."
    		::= { znyxPsMibZX7100FABRIC 25 }

	zZX7100FABRICVPDVR OBJECT-TYPE
   		SYNTAX DisplayString
   		ACCESS read-only
   	 	STATUS     mandatory
   		DESCRIPTION
    	    		"The Reset CPLD Version."
    		::= { znyxPsMibZX7100FABRIC 26 }

	zZX7100FABRICVPDVL OBJECT-TYPE
   		SYNTAX DisplayString
   		ACCESS read-only
   	 	STATUS     mandatory
   		DESCRIPTION
    	    		"The LED CPLD Version."
    		::= { znyxPsMibZX7100FABRIC 27 }

	zZX7100FABRICVPDVZ OBJECT-TYPE
   		SYNTAX DisplayString
   		ACCESS read-only
   	 	STATUS     mandatory
   		DESCRIPTION
    	    		"The ZMON Version."
    		::= { znyxPsMibZX7100FABRIC 28 }

	zZX7100FABRICVPDY1 OBJECT-TYPE
   		SYNTAX DisplayString
   		ACCESS read-only
   	 	STATUS     mandatory
   		DESCRIPTION
    	    		"The Manufacturer ID."
    		::= { znyxPsMibZX7100FABRIC 29 }

	zZX7100FABRICVPDY2 OBJECT-TYPE
   		SYNTAX DisplayString
   		ACCESS read-only
   	 	STATUS     mandatory
   		DESCRIPTION
    	    		"The Board ID."
    		::= { znyxPsMibZX7100FABRIC 30 }

	zZX7100FABRICVPDY3 OBJECT-TYPE
   		SYNTAX DisplayString
   		ACCESS read-only
   	 	STATUS     mandatory
   		DESCRIPTION
    	    		"The Data CLEI."
    		::= { znyxPsMibZX7100FABRIC 31 }

	zZX7100FABRICVPDY4 OBJECT-TYPE
   		SYNTAX DisplayString
   		ACCESS read-only
   	 	STATUS     mandatory
   		DESCRIPTION
    	    		"The Data PEC."
    		::= { znyxPsMibZX7100FABRIC 32 }

	zZX7100FABRICVPDY5 OBJECT-TYPE
   		SYNTAX DisplayString
   		ACCESS read-only
   	 	STATUS     mandatory
   		DESCRIPTION
    	    		"The Release Number."
    		::= { znyxPsMibZX7100FABRIC 33 }

	END
