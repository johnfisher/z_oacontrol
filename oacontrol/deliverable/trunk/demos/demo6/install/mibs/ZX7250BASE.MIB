--==========================================================================
--
--	ZX7250BASE.MIB
--
--	ZNYX ZX7250BASE SNMP MIB
--
--==========================================================================
--
--	(c) Copyright 2001 ZNYX Networks, Inc.
--	All rights reserved.
--
--==========================================================================


	ZX7250BASE-MIB DEFINITIONS ::= BEGIN

	IMPORTS
		enterprises, NetworkAddress, IpAddress, Counter,
		Gauge, TimeTicks, OBJECT-TYPE
			FROM RFC1155-SMI
		znyxProductSpecificMib
			FROM ZNYX-MIB;

	-- Conventions

	DisplayString ::= OCTET STRING



	znyxPsMibZX7250BASE		OBJECT IDENTIFIER ::= { znyxProductSpecificMib 12 }

	zZX7250BASEGeoPins OBJECT-TYPE
		SYNTAX  DisplayString (SIZE (0..255))
		ACCESS  read-only
		STATUS  mandatory
		DESCRIPTION
			"This object returns a string identifying
			 the shelf and the slot within the shelf
			 the switch is located in."
		::= { znyxPsMibZX7250BASE 1 }

	zZX7250BASEInternalFaultLedControl OBJECT-TYPE
		SYNTAX  INTEGER {
			off(1),
			on(2),
			other(3)	-- driven by other control
			}
		ACCESS  read-write
		STATUS  mandatory
		DESCRIPTION
			"This object is used to determine how the
			 Internal Fault LED is driven."
		::= { znyxPsMibZX7250BASE 2 }

	zZX7250BASEInternalFaultLedStatus OBJECT-TYPE
		SYNTAX  INTEGER {
			off(1),
			on(2)
			}
		ACCESS  read-only
		STATUS  mandatory
		DESCRIPTION
			"This object is used to determine the
			 current Internal Fault LED status."
		::= { znyxPsMibZX7250BASE 3 }

	zZX7250BASEExternalFaultLedControl OBJECT-TYPE
		SYNTAX  INTEGER {
			off(1),
			on(2),
			other(3)	-- driven by other control
			}
		ACCESS  read-write
		STATUS  mandatory
		DESCRIPTION
			"This object is used to determine how the
			 External Fault LED is driven."
		::= { znyxPsMibZX7250BASE 4 }

	zZX7250BASEExternalFaultLedStatus OBJECT-TYPE
		SYNTAX  INTEGER {
			off(1),
			on(2)
			}
		ACCESS  read-only
		STATUS  mandatory
		DESCRIPTION
			"This object is used to determine the
			 current External Fault LED status."
		::= { znyxPsMibZX7250BASE 5 }

	zZX7250BASEOpenArchVersion OBJECT-TYPE
   		SYNTAX DisplayString
   		ACCESS read-only
   	 	STATUS     mandatory
   		DESCRIPTION
    	    		"The Open Architect software version."
    		::= { znyxPsMibZX7250BASE 6 }

	zZX7250BASELinkCtrlTable OBJECT-TYPE
	    	SYNTAX      SEQUENCE OF ZZX7250BASELinkCtrlEntry
  		ACCESS  not-accessible
    		STATUS      mandatory
    		DESCRIPTION
      	    	"A table containing link control information for each port
		       available on the device."
    		::= { znyxPsMibZX7250BASE 7 }

	zZX7250BASELinkCtrlEntry OBJECT-TYPE
 		SYNTAX      ZZX7250BASELinkCtrlEntry
    		ACCESS  not-accessible
    		STATUS      mandatory
    		DESCRIPTION
      		"Link control information for each port available on the
			 device."
   		INDEX   { zZX7250BASELinkCtrlPort }
    		::= { zZX7250BASELinkCtrlTable 1 }

 	ZZX7250BASELinkCtrlEntry ::=
  		SEQUENCE {
			zZX7250BASELinkCtrlPort
				INTEGER,
			zZX7250BASELinkCtrlState
				INTEGER,
			zZX7250BASELinkCtrlSpeed
				INTEGER
    		}

	zZX7250BASELinkCtrlPort OBJECT-TYPE
		SYNTAX      INTEGER (1..65535)
		ACCESS  not-accessible
		STATUS      mandatory
		DESCRIPTION
		"The port number associated with this Link Control entry."
		::= { zZX7250BASELinkCtrlEntry 1 }

	zZX7250BASELinkCtrlState OBJECT-TYPE
    		SYNTAX      INTEGER { up (1), down (2) }
    		ACCESS  read-write
    		STATUS      mandatory
    		DESCRIPTION
        		"The link control state of the port."
    		::= { zZX7250BASELinkCtrlEntry 2 }

	zZX7250BASELinkCtrlSpeed OBJECT-TYPE
    		SYNTAX      INTEGER  { auto(1), n100fd(2), n100hd(3), n10fd (4), n10hd(5), n1000fd(6), n1000hd(7), n10000fd(8) }
    		ACCESS  read-write
    		STATUS      mandatory
    		DESCRIPTION
        		"The link control speed of the port. Changes to this speed
			 require the port to be in the down state."
    		::= { zZX7250BASELinkCtrlEntry 3 }

	-- Vital Product Data (VPD)

	zZX7250BASEVPDPN OBJECT-TYPE
   		SYNTAX DisplayString
   		ACCESS read-only
   	 	STATUS     mandatory
   		DESCRIPTION
    	    		"The VPD Part Number."
    		::= { znyxPsMibZX7250BASE 8 }

	zZX7250BASEVPDSN OBJECT-TYPE
   		SYNTAX DisplayString
   		ACCESS read-only
   	 	STATUS     mandatory
   		DESCRIPTION
    	    		"The VPD Serial Number."
    		::= { znyxPsMibZX7250BASE 9 }

	zZX7250BASEVPDV0 OBJECT-TYPE
   		SYNTAX DisplayString
   		ACCESS read-only
   	 	STATUS     mandatory
   		DESCRIPTION
    	    		"The VPD Mac Address."
    		::= { znyxPsMibZX7250BASE 10 }

	zZX7250BASEVPDV1 OBJECT-TYPE
   		SYNTAX DisplayString
   		ACCESS read-only
   	 	STATUS     mandatory
   		DESCRIPTION
    	    		"The VPD Mac Address Number."
    		::= { znyxPsMibZX7250BASE 11 }

	zZX7250BASEVPDV2 OBJECT-TYPE
   		SYNTAX DisplayString
   		ACCESS read-only
   	 	STATUS     mandatory
   		DESCRIPTION
    	    		"The PPC 82xx Memory Subsystem."
    		::= { znyxPsMibZX7250BASE 12 }

	zZX7250BASEVPDV3 OBJECT-TYPE
   		SYNTAX DisplayString
   		ACCESS read-only
   	 	STATUS     mandatory
   		DESCRIPTION
    	    		"The BCM 56xx Memory Subsystem."
    		::= { znyxPsMibZX7250BASE 13 }

	zZX7250BASEVPDV4 OBJECT-TYPE
   		SYNTAX DisplayString
   		ACCESS read-only
   	 	STATUS     mandatory
   		DESCRIPTION
    	    		"The Boot Flash Subsystem."
    		::= { znyxPsMibZX7250BASE 14 }

	zZX7250BASEVPDV5 OBJECT-TYPE
   		SYNTAX DisplayString
   		ACCESS read-only
   	 	STATUS     mandatory
   		DESCRIPTION
    	    		"The Application Flash Subsystem."
    		::= { znyxPsMibZX7250BASE 15 }

	zZX7250BASEVPDV6 OBJECT-TYPE
   		SYNTAX DisplayString
   		ACCESS read-only
   	 	STATUS     mandatory
   		DESCRIPTION
    	    		"The Firmware Revision."
    		::= { znyxPsMibZX7250BASE 16 }

	zZX7250BASEVPDV7 OBJECT-TYPE
   		SYNTAX DisplayString
   		ACCESS read-only
   	 	STATUS     mandatory
   		DESCRIPTION
    	    		"The Reset Counter."
    		::= { znyxPsMibZX7250BASE 17 }

	zZX7250BASEVPDV8 OBJECT-TYPE
   		SYNTAX DisplayString
   		ACCESS read-only
   	 	STATUS     mandatory
   		DESCRIPTION
    	    		"The Kernel Runtime."
    		::= { znyxPsMibZX7250BASE 18 }

	zZX7250BASEVPDV9 OBJECT-TYPE
   		SYNTAX DisplayString
   		ACCESS read-only
   	 	STATUS     mandatory
   		DESCRIPTION
    	    		"The VPD Revision."
    		::= { znyxPsMibZX7250BASE 19 }

	zZX7250BASEVPDVA OBJECT-TYPE
   		SYNTAX DisplayString
   		ACCESS read-only
   	 	STATUS     mandatory
   		DESCRIPTION
    	    		"The Adapter ID."
    		::= { znyxPsMibZX7250BASE 20 }

	zZX7250BASEVPDVB OBJECT-TYPE
   		SYNTAX DisplayString
   		ACCESS read-only
   	 	STATUS     mandatory
   		DESCRIPTION
    	    		"The Model Number."
    		::= { znyxPsMibZX7250BASE 21 }

	zZX7250BASEVPDVS OBJECT-TYPE
   		SYNTAX DisplayString
   		ACCESS read-only
   	 	STATUS     mandatory
   		DESCRIPTION
    	    		"The Logical Slot Number."
    		::= { znyxPsMibZX7250BASE 22 }

	zZX7250BASEVPDVT OBJECT-TYPE
   		SYNTAX DisplayString
   		ACCESS read-only
   	 	STATUS     mandatory
   		DESCRIPTION
    	    		"The Geographical Shelf Address."
    		::= { znyxPsMibZX7250BASE 23 }

	zZX7250BASEVPDVP OBJECT-TYPE
   		SYNTAX DisplayString
   		ACCESS read-only
   	 	STATUS     mandatory
   		DESCRIPTION
    	    		"The IPMC Version."
    		::= { znyxPsMibZX7250BASE 24 }

	zZX7250BASEVPDVM OBJECT-TYPE
   		SYNTAX DisplayString
   		ACCESS read-only
   	 	STATUS     mandatory
   		DESCRIPTION
    	    		"The Main CPLD Version."
    		::= { znyxPsMibZX7250BASE 25 }

	zZX7250BASEVPDVR OBJECT-TYPE
   		SYNTAX DisplayString
   		ACCESS read-only
   	 	STATUS     mandatory
   		DESCRIPTION
    	    		"The Reset CPLD Version."
    		::= { znyxPsMibZX7250BASE 26 }

	zZX7250BASEVPDVL OBJECT-TYPE
   		SYNTAX DisplayString
   		ACCESS read-only
   	 	STATUS     mandatory
   		DESCRIPTION
    	    		"The LED CPLD Version."
    		::= { znyxPsMibZX7250BASE 27 }

	zZX7250BASEVPDVZ OBJECT-TYPE
   		SYNTAX DisplayString
   		ACCESS read-only
   	 	STATUS     mandatory
   		DESCRIPTION
    	    		"The ZMON Version."
    		::= { znyxPsMibZX7250BASE 28 }

	zZX7250BASEVPDY1 OBJECT-TYPE
   		SYNTAX DisplayString
   		ACCESS read-only
   	 	STATUS     mandatory
   		DESCRIPTION
    	    		"The Manufacturer ID."
    		::= { znyxPsMibZX7250BASE 29 }

	zZX7250BASEVPDY2 OBJECT-TYPE
   		SYNTAX DisplayString
   		ACCESS read-only
   	 	STATUS     mandatory
   		DESCRIPTION
    	    		"The Board ID."
    		::= { znyxPsMibZX7250BASE 30 }

	zZX7250BASEVPDY3 OBJECT-TYPE
   		SYNTAX DisplayString
   		ACCESS read-only
   	 	STATUS     mandatory
   		DESCRIPTION
    	    		"The Data CLEI."
    		::= { znyxPsMibZX7250BASE 31 }

	zZX7250BASEVPDY4 OBJECT-TYPE
   		SYNTAX DisplayString
   		ACCESS read-only
   	 	STATUS     mandatory
   		DESCRIPTION
    	    		"The Data PEC."
    		::= { znyxPsMibZX7250BASE 32 }

	zZX7250BASEVPDY5 OBJECT-TYPE
   		SYNTAX DisplayString
   		ACCESS read-only
   	 	STATUS     mandatory
   		DESCRIPTION
    	    		"The Release Number."
    		::= { znyxPsMibZX7250BASE 33 }

	END
