--==========================================================================
--
--	ZX6200.MIB
--
--	ZNYX ZX6200 SNMP MIB
--
--==========================================================================
--
--	(c) Copyright 2001 ZNYX Networks, Inc.
--	All rights reserved.
--
--==========================================================================


	ZX6200-MIB DEFINITIONS ::= BEGIN

	IMPORTS
		enterprises, NetworkAddress, IpAddress, Counter,
		Gauge, TimeTicks, OBJECT-TYPE
			FROM RFC1155-SMI
		znyxProductSpecificMib
			FROM ZNYX-MIB;

	-- Conventions

	DisplayString ::= OCTET STRING



	znyxPsMibZX6200		OBJECT IDENTIFIER ::= { znyxProductSpecificMib 16 }

	zZX6200GeoPins OBJECT-TYPE
		SYNTAX  DisplayString (SIZE (0..255))
		ACCESS  read-only
		STATUS  mandatory
		DESCRIPTION
			"This object returns a string identifying
			 the shelf and the slot within the shelf
			 the switch is located in."
		::= { znyxPsMibZX6200 1 }

	zZX6200InternalFaultLedControl OBJECT-TYPE
		SYNTAX  INTEGER {
			off(1),
			on(2),
			other(3)	-- driven by other control
			}
		ACCESS  read-write
		STATUS  mandatory
		DESCRIPTION
			"This object is used to determine how the
			 Internal Fault LED is driven."
		::= { znyxPsMibZX6200 2 }

	zZX6200InternalFaultLedStatus OBJECT-TYPE
		SYNTAX  INTEGER {
			off(1),
			on(2)
			}
		ACCESS  read-only
		STATUS  mandatory
		DESCRIPTION
			"This object is used to determine the
			 current Internal Fault LED status."
		::= { znyxPsMibZX6200 3 }

	zZX6200ExternalFaultLedControl OBJECT-TYPE
		SYNTAX  INTEGER {
			off(1),
			on(2),
			other(3)	-- driven by other control
			}
		ACCESS  read-write
		STATUS  mandatory
		DESCRIPTION
			"This object is used to determine how the
			 External Fault LED is driven."
		::= { znyxPsMibZX6200 4 }

	zZX6200ExternalFaultLedStatus OBJECT-TYPE
		SYNTAX  INTEGER {
			off(1),
			on(2)
			}
		ACCESS  read-only
		STATUS  mandatory
		DESCRIPTION
			"This object is used to determine the
			 current External Fault LED status."
		::= { znyxPsMibZX6200 5 }

	zZX6200OpenArchVersion OBJECT-TYPE
   		SYNTAX DisplayString
   		ACCESS read-only
   	 	STATUS     mandatory
   		DESCRIPTION
    	    		"The Open Architect software version."
    		::= { znyxPsMibZX6200 6 }

	zZX6200LinkCtrlTable OBJECT-TYPE
	    	SYNTAX      SEQUENCE OF ZZX6200LinkCtrlEntry
  		ACCESS  not-accessible
    		STATUS      mandatory
    		DESCRIPTION
      	    	"A table containing link control information for each port
		       available on the device."
    		::= { znyxPsMibZX6200 7 }

	zZX6200LinkCtrlEntry OBJECT-TYPE
 		SYNTAX      ZZX6200LinkCtrlEntry
    		ACCESS  not-accessible
    		STATUS      mandatory
    		DESCRIPTION
      		"Link control information for each port available on the
			 device."
   		INDEX   { zZX6200LinkCtrlPort }
    		::= { zZX6200LinkCtrlTable 1 }

 	ZZX6200LinkCtrlEntry ::=
  		SEQUENCE {
			zZX6200LinkCtrlPort
				INTEGER,
			zZX6200LinkCtrlState
				INTEGER,
			zZX6200LinkCtrlSpeed
				INTEGER
    		}

	zZX6200LinkCtrlPort OBJECT-TYPE
		SYNTAX      INTEGER (1..65535)
		ACCESS  not-accessible
		STATUS      mandatory
		DESCRIPTION
		"The port number associated with this Link Control entry."
		::= { zZX6200LinkCtrlEntry 1 }

	zZX6200LinkCtrlState OBJECT-TYPE
    		SYNTAX      INTEGER { up (1), down (2) }
    		ACCESS  read-write
    		STATUS      mandatory
    		DESCRIPTION
        		"The link control state of the port."
    		::= { zZX6200LinkCtrlEntry 2 }

	zZX6200LinkCtrlSpeed OBJECT-TYPE
    		SYNTAX      INTEGER  { auto(1), n100fd(2), n100hd(3), n10fd (4), n10hd(5), n1000fd(6), n1000hd(7), n10000fd(8) }
    		ACCESS  read-write
    		STATUS      mandatory
    		DESCRIPTION
        		"The link control speed of the port. Changes to this speed
			 require the port to be in the down state."
    		::= { zZX6200LinkCtrlEntry 3 }

	-- Vital Product Data (VPD)

	zZX6200VPDPN OBJECT-TYPE
   		SYNTAX DisplayString
   		ACCESS read-only
   	 	STATUS     mandatory
   		DESCRIPTION
    	    		"The VPD Part Number."
    		::= { znyxPsMibZX6200 8 }

	zZX6200VPDSN OBJECT-TYPE
   		SYNTAX DisplayString
   		ACCESS read-only
   	 	STATUS     mandatory
   		DESCRIPTION
    	    		"The VPD Serial Number."
    		::= { znyxPsMibZX6200 9 }

	zZX6200VPDV0 OBJECT-TYPE
   		SYNTAX DisplayString
   		ACCESS read-only
   	 	STATUS     mandatory
   		DESCRIPTION
    	    		"The VPD Mac Address."
    		::= { znyxPsMibZX6200 10 }

	zZX6200VPDV1 OBJECT-TYPE
   		SYNTAX DisplayString
   		ACCESS read-only
   	 	STATUS     mandatory
   		DESCRIPTION
    	    		"The VPD Mac Address Number."
    		::= { znyxPsMibZX6200 11 }

	zZX6200VPDV2 OBJECT-TYPE
   		SYNTAX DisplayString
   		ACCESS read-only
   	 	STATUS     mandatory
   		DESCRIPTION
    	    		"The PPC 82xx Memory Subsystem."
    		::= { znyxPsMibZX6200 12 }

	zZX6200VPDV3 OBJECT-TYPE
   		SYNTAX DisplayString
   		ACCESS read-only
   	 	STATUS     mandatory
   		DESCRIPTION
    	    		"The BCM 56xx Memory Subsystem."
    		::= { znyxPsMibZX6200 13 }

	zZX6200VPDV4 OBJECT-TYPE
   		SYNTAX DisplayString
   		ACCESS read-only
   	 	STATUS     mandatory
   		DESCRIPTION
    	    		"The Boot Flash Subsystem."
    		::= { znyxPsMibZX6200 14 }

	zZX6200VPDV5 OBJECT-TYPE
   		SYNTAX DisplayString
   		ACCESS read-only
   	 	STATUS     mandatory
   		DESCRIPTION
    	    		"The Application Flash Subsystem."
    		::= { znyxPsMibZX6200 15 }

	zZX6200VPDV6 OBJECT-TYPE
   		SYNTAX DisplayString
   		ACCESS read-only
   	 	STATUS     mandatory
   		DESCRIPTION
    	    		"The Firmware Revision."
    		::= { znyxPsMibZX6200 16 }

	zZX6200VPDV7 OBJECT-TYPE
   		SYNTAX DisplayString
   		ACCESS read-only
   	 	STATUS     mandatory
   		DESCRIPTION
    	    		"The Reset Counter."
    		::= { znyxPsMibZX6200 17 }

	zZX6200VPDV8 OBJECT-TYPE
   		SYNTAX DisplayString
   		ACCESS read-only
   	 	STATUS     mandatory
   		DESCRIPTION
    	    		"The Kernel Runtime."
    		::= { znyxPsMibZX6200 18 }

	zZX6200VPDV9 OBJECT-TYPE
   		SYNTAX DisplayString
   		ACCESS read-only
   	 	STATUS     mandatory
   		DESCRIPTION
    	    		"The VPD Revision."
    		::= { znyxPsMibZX6200 19 }

	zZX6200VPDVA OBJECT-TYPE
   		SYNTAX DisplayString
   		ACCESS read-only
   	 	STATUS     mandatory
   		DESCRIPTION
    	    		"The Adapter ID."
    		::= { znyxPsMibZX6200 20 }

	zZX6200VPDVB OBJECT-TYPE
   		SYNTAX DisplayString
   		ACCESS read-only
   	 	STATUS     mandatory
   		DESCRIPTION
    	    		"The Model Number."
    		::= { znyxPsMibZX6200 21 }

	zZX6200VPDVS OBJECT-TYPE
   		SYNTAX DisplayString
   		ACCESS read-only
   	 	STATUS     mandatory
   		DESCRIPTION
    	    		"The Logical Slot Number."
    		::= { znyxPsMibZX6200 22 }

	zZX6200VPDVT OBJECT-TYPE
   		SYNTAX DisplayString
   		ACCESS read-only
   	 	STATUS     mandatory
   		DESCRIPTION
    	    		"The Geographical Shelf Address."
    		::= { znyxPsMibZX6200 23 }

	zZX6200VPDVP OBJECT-TYPE
   		SYNTAX DisplayString
   		ACCESS read-only
   	 	STATUS     mandatory
   		DESCRIPTION
    	    		"The IPMC Version."
    		::= { znyxPsMibZX6200 24 }

	zZX6200VPDVM OBJECT-TYPE
   		SYNTAX DisplayString
   		ACCESS read-only
   	 	STATUS     mandatory
   		DESCRIPTION
    	    		"The Main CPLD Version."
    		::= { znyxPsMibZX6200 25 }

	zZX6200VPDVR OBJECT-TYPE
   		SYNTAX DisplayString
   		ACCESS read-only
   	 	STATUS     mandatory
   		DESCRIPTION
    	    		"The Reset CPLD Version."
    		::= { znyxPsMibZX6200 26 }

	zZX6200VPDVL OBJECT-TYPE
   		SYNTAX DisplayString
   		ACCESS read-only
   	 	STATUS     mandatory
   		DESCRIPTION
    	    		"The LED CPLD Version."
    		::= { znyxPsMibZX6200 27 }

	zZX6200VPDVZ OBJECT-TYPE
   		SYNTAX DisplayString
   		ACCESS read-only
   	 	STATUS     mandatory
   		DESCRIPTION
    	    		"The ZMON Version."
    		::= { znyxPsMibZX6200 28 }

	zZX6200VPDY1 OBJECT-TYPE
   		SYNTAX DisplayString
   		ACCESS read-only
   	 	STATUS     mandatory
   		DESCRIPTION
    	    		"The Manufacturer ID."
    		::= { znyxPsMibZX6200 29 }

	zZX6200VPDY2 OBJECT-TYPE
   		SYNTAX DisplayString
   		ACCESS read-only
   	 	STATUS     mandatory
   		DESCRIPTION
    	    		"The Board ID."
    		::= { znyxPsMibZX6200 30 }

	zZX6200VPDY3 OBJECT-TYPE
   		SYNTAX DisplayString
   		ACCESS read-only
   	 	STATUS     mandatory
   		DESCRIPTION
    	    		"The Data CLEI."
    		::= { znyxPsMibZX6200 31 }

	zZX6200VPDY4 OBJECT-TYPE
   		SYNTAX DisplayString
   		ACCESS read-only
   	 	STATUS     mandatory
   		DESCRIPTION
    	    		"The Data PEC."
    		::= { znyxPsMibZX6200 32 }

	zZX6200VPDY5 OBJECT-TYPE
   		SYNTAX DisplayString
   		ACCESS read-only
   	 	STATUS     mandatory
   		DESCRIPTION
    	    		"The Release Number."
    		::= { znyxPsMibZX6200 33 }

	END
