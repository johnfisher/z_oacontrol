--==========================================================================
--
--	ZX7200BASE.MIB
--
--	ZNYX ZX7200BASE SNMP MIB
--
--==========================================================================
--
--	(c) Copyright 2001 ZNYX Networks, Inc.
--	All rights reserved.
--
--==========================================================================


	ZX7200BASE-MIB DEFINITIONS ::= BEGIN

	IMPORTS
		enterprises, NetworkAddress, IpAddress, Counter,
		Gauge, TimeTicks, OBJECT-TYPE
			FROM RFC1155-SMI
		znyxProductSpecificMib
			FROM ZNYX-MIB;

	-- Conventions

	DisplayString ::= OCTET STRING



	znyxPsMibZX7200BASE		OBJECT IDENTIFIER ::= { znyxProductSpecificMib 10 }

	zZX7200BASEGeoPins OBJECT-TYPE
		SYNTAX  DisplayString (SIZE (0..255))
		ACCESS  read-only
		STATUS  mandatory
		DESCRIPTION
			"This object returns a string identifying
			 the shelf and the slot within the shelf
			 the switch is located in."
		::= { znyxPsMibZX7200BASE 1 }

	zZX7200BASEInternalFaultLedControl OBJECT-TYPE
		SYNTAX  INTEGER {
			off(1),
			on(2),
			other(3)	-- driven by other control
			}
		ACCESS  read-write
		STATUS  mandatory
		DESCRIPTION
			"This object is used to determine how the
			 Internal Fault LED is driven."
		::= { znyxPsMibZX7200BASE 2 }

	zZX7200BASEInternalFaultLedStatus OBJECT-TYPE
		SYNTAX  INTEGER {
			off(1),
			on(2)
			}
		ACCESS  read-only
		STATUS  mandatory
		DESCRIPTION
			"This object is used to determine the
			 current Internal Fault LED status."
		::= { znyxPsMibZX7200BASE 3 }

	zZX7200BASEExternalFaultLedControl OBJECT-TYPE
		SYNTAX  INTEGER {
			off(1),
			on(2),
			other(3)	-- driven by other control
			}
		ACCESS  read-write
		STATUS  mandatory
		DESCRIPTION
			"This object is used to determine how the
			 External Fault LED is driven."
		::= { znyxPsMibZX7200BASE 4 }

	zZX7200BASEExternalFaultLedStatus OBJECT-TYPE
		SYNTAX  INTEGER {
			off(1),
			on(2)
			}
		ACCESS  read-only
		STATUS  mandatory
		DESCRIPTION
			"This object is used to determine the
			 current External Fault LED status."
		::= { znyxPsMibZX7200BASE 5 }

	zZX7200BASEOpenArchVersion OBJECT-TYPE
   		SYNTAX DisplayString
   		ACCESS read-only
   	 	STATUS     mandatory
   		DESCRIPTION
    	    		"The Open Architect software version."
    		::= { znyxPsMibZX7200BASE 6 }

	zZX7200BASELinkCtrlTable OBJECT-TYPE
	    	SYNTAX      SEQUENCE OF ZZX7200BASELinkCtrlEntry
  		ACCESS  not-accessible
    		STATUS      mandatory
    		DESCRIPTION
      	    	"A table containing link control information for each port
		       available on the device."
    		::= { znyxPsMibZX7200BASE 7 }

	zZX7200BASELinkCtrlEntry OBJECT-TYPE
 		SYNTAX      ZZX7200BASELinkCtrlEntry
    		ACCESS  not-accessible
    		STATUS      mandatory
    		DESCRIPTION
      		"Link control information for each port available on the
			 device."
   		INDEX   { zZX7200BASELinkCtrlPort }
    		::= { zZX7200BASELinkCtrlTable 1 }

 	ZZX7200BASELinkCtrlEntry ::=
  		SEQUENCE {
			zZX7200BASELinkCtrlPort
				INTEGER,
			zZX7200BASELinkCtrlState
				INTEGER,
			zZX7200BASELinkCtrlSpeed
				INTEGER
    		}

	zZX7200BASELinkCtrlPort OBJECT-TYPE
		SYNTAX      INTEGER (1..65535)
		ACCESS  not-accessible
		STATUS      mandatory
		DESCRIPTION
		"The port number associated with this Link Control entry."
		::= { zZX7200BASELinkCtrlEntry 1 }

	zZX7200BASELinkCtrlState OBJECT-TYPE
    		SYNTAX      INTEGER { up (1), down (2) }
    		ACCESS  read-write
    		STATUS      mandatory
    		DESCRIPTION
        		"The link control state of the port."
    		::= { zZX7200BASELinkCtrlEntry 2 }

	zZX7200BASELinkCtrlSpeed OBJECT-TYPE
    		SYNTAX      INTEGER  { auto(1), n100fd(2), n100hd(3), n10fd (4), n10hd(5), n1000fd(6), n1000hd(7), n10000fd(8) }
    		ACCESS  read-write
    		STATUS      mandatory
    		DESCRIPTION
        		"The link control speed of the port. Changes to this speed
			 require the port to be in the down state."
    		::= { zZX7200BASELinkCtrlEntry 3 }

	-- Vital Product Data (VPD)

	zZX7200BASEVPDPN OBJECT-TYPE
   		SYNTAX DisplayString
   		ACCESS read-only
   	 	STATUS     mandatory
   		DESCRIPTION
    	    		"The VPD Part Number."
    		::= { znyxPsMibZX7200BASE 8 }

	zZX7200BASEVPDSN OBJECT-TYPE
   		SYNTAX DisplayString
   		ACCESS read-only
   	 	STATUS     mandatory
   		DESCRIPTION
    	    		"The VPD Serial Number."
    		::= { znyxPsMibZX7200BASE 9 }

	zZX7200BASEVPDV0 OBJECT-TYPE
   		SYNTAX DisplayString
   		ACCESS read-only
   	 	STATUS     mandatory
   		DESCRIPTION
    	    		"The VPD Mac Address."
    		::= { znyxPsMibZX7200BASE 10 }

	zZX7200BASEVPDV1 OBJECT-TYPE
   		SYNTAX DisplayString
   		ACCESS read-only
   	 	STATUS     mandatory
   		DESCRIPTION
    	    		"The VPD Mac Address Number."
    		::= { znyxPsMibZX7200BASE 11 }

	zZX7200BASEVPDV2 OBJECT-TYPE
   		SYNTAX DisplayString
   		ACCESS read-only
   	 	STATUS     mandatory
   		DESCRIPTION
    	    		"The PPC 82xx Memory Subsystem."
    		::= { znyxPsMibZX7200BASE 12 }

	zZX7200BASEVPDV3 OBJECT-TYPE
   		SYNTAX DisplayString
   		ACCESS read-only
   	 	STATUS     mandatory
   		DESCRIPTION
    	    		"The BCM 56xx Memory Subsystem."
    		::= { znyxPsMibZX7200BASE 13 }

	zZX7200BASEVPDV4 OBJECT-TYPE
   		SYNTAX DisplayString
   		ACCESS read-only
   	 	STATUS     mandatory
   		DESCRIPTION
    	    		"The Boot Flash Subsystem."
    		::= { znyxPsMibZX7200BASE 14 }

	zZX7200BASEVPDV5 OBJECT-TYPE
   		SYNTAX DisplayString
   		ACCESS read-only
   	 	STATUS     mandatory
   		DESCRIPTION
    	    		"The Application Flash Subsystem."
    		::= { znyxPsMibZX7200BASE 15 }

	zZX7200BASEVPDV6 OBJECT-TYPE
   		SYNTAX DisplayString
   		ACCESS read-only
   	 	STATUS     mandatory
   		DESCRIPTION
    	    		"The Firmware Revision."
    		::= { znyxPsMibZX7200BASE 16 }

	zZX7200BASEVPDV7 OBJECT-TYPE
   		SYNTAX DisplayString
   		ACCESS read-only
   	 	STATUS     mandatory
   		DESCRIPTION
    	    		"The Reset Counter."
    		::= { znyxPsMibZX7200BASE 17 }

	zZX7200BASEVPDV8 OBJECT-TYPE
   		SYNTAX DisplayString
   		ACCESS read-only
   	 	STATUS     mandatory
   		DESCRIPTION
    	    		"The Kernel Runtime."
    		::= { znyxPsMibZX7200BASE 18 }

	zZX7200BASEVPDV9 OBJECT-TYPE
   		SYNTAX DisplayString
   		ACCESS read-only
   	 	STATUS     mandatory
   		DESCRIPTION
    	    		"The VPD Revision."
    		::= { znyxPsMibZX7200BASE 19 }

	zZX7200BASEVPDVA OBJECT-TYPE
   		SYNTAX DisplayString
   		ACCESS read-only
   	 	STATUS     mandatory
   		DESCRIPTION
    	    		"The Adapter ID."
    		::= { znyxPsMibZX7200BASE 20 }

	zZX7200BASEVPDVB OBJECT-TYPE
   		SYNTAX DisplayString
   		ACCESS read-only
   	 	STATUS     mandatory
   		DESCRIPTION
    	    		"The Model Number."
    		::= { znyxPsMibZX7200BASE 21 }

	zZX7200BASEVPDVS OBJECT-TYPE
   		SYNTAX DisplayString
   		ACCESS read-only
   	 	STATUS     mandatory
   		DESCRIPTION
    	    		"The Logical Slot Number."
    		::= { znyxPsMibZX7200BASE 22 }

	zZX7200BASEVPDVT OBJECT-TYPE
   		SYNTAX DisplayString
   		ACCESS read-only
   	 	STATUS     mandatory
   		DESCRIPTION
    	    		"The Geographical Shelf Address."
    		::= { znyxPsMibZX7200BASE 23 }

	zZX7200BASEVPDVP OBJECT-TYPE
   		SYNTAX DisplayString
   		ACCESS read-only
   	 	STATUS     mandatory
   		DESCRIPTION
    	    		"The IPMC Version."
    		::= { znyxPsMibZX7200BASE 24 }

	zZX7200BASEVPDVM OBJECT-TYPE
   		SYNTAX DisplayString
   		ACCESS read-only
   	 	STATUS     mandatory
   		DESCRIPTION
    	    		"The Main CPLD Version."
    		::= { znyxPsMibZX7200BASE 25 }

	zZX7200BASEVPDVR OBJECT-TYPE
   		SYNTAX DisplayString
   		ACCESS read-only
   	 	STATUS     mandatory
   		DESCRIPTION
    	    		"The Reset CPLD Version."
    		::= { znyxPsMibZX7200BASE 26 }

	zZX7200BASEVPDVL OBJECT-TYPE
   		SYNTAX DisplayString
   		ACCESS read-only
   	 	STATUS     mandatory
   		DESCRIPTION
    	    		"The LED CPLD Version."
    		::= { znyxPsMibZX7200BASE 27 }

	zZX7200BASEVPDVZ OBJECT-TYPE
   		SYNTAX DisplayString
   		ACCESS read-only
   	 	STATUS     mandatory
   		DESCRIPTION
    	    		"The ZMON Version."
    		::= { znyxPsMibZX7200BASE 28 }

	zZX7200BASEVPDY1 OBJECT-TYPE
   		SYNTAX DisplayString
   		ACCESS read-only
   	 	STATUS     mandatory
   		DESCRIPTION
    	    		"The Manufacturer ID."
    		::= { znyxPsMibZX7200BASE 29 }

	zZX7200BASEVPDY2 OBJECT-TYPE
   		SYNTAX DisplayString
   		ACCESS read-only
   	 	STATUS     mandatory
   		DESCRIPTION
    	    		"The Board ID."
    		::= { znyxPsMibZX7200BASE 30 }

	zZX7200BASEVPDY3 OBJECT-TYPE
   		SYNTAX DisplayString
   		ACCESS read-only
   	 	STATUS     mandatory
   		DESCRIPTION
    	    		"The Data CLEI."
    		::= { znyxPsMibZX7200BASE 31 }

	zZX7200BASEVPDY4 OBJECT-TYPE
   		SYNTAX DisplayString
   		ACCESS read-only
   	 	STATUS     mandatory
   		DESCRIPTION
    	    		"The Data PEC."
    		::= { znyxPsMibZX7200BASE 32 }

	zZX7200BASEVPDY5 OBJECT-TYPE
   		SYNTAX DisplayString
   		ACCESS read-only
   	 	STATUS     mandatory
   		DESCRIPTION
    	    		"The Release Number."
    		::= { znyxPsMibZX7200BASE 33 }

	END
